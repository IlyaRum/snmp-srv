NTC-SNMP-MIB -- { iso org(3) dod(6) internet(1) private(4) enterprises(1) 63573 }
DEFINITIONS ::= BEGIN

IMPORTS
    MODULE-IDENTITY, OBJECT-TYPE, NOTIFICATION-TYPE,
    Integer32, Gauge32, TimeTicks, IpAddress, Counter32,
    enterprises, snmpModules
        FROM SNMPv2-SMI
    TEXTUAL-CONVENTION, DisplayString, DateAndTime,
    TruthValue, RowStatus, TimeStamp
        FROM SNMPv2-TC
    MODULE-COMPLIANCE, OBJECT-GROUP, NOTIFICATION-GROUP
        FROM SNMPv2-CONF;

-- Идентификация модуля

ntc MODULE-IDENTITY
    LAST-UPDATED "202605221625Z"
    ORGANIZATION "NTC"
    CONTACT-INFO "IlyaR"
    DESCRIPTION
        "MIB для мониторинга сервисов Арбитра и отправки трапов в ESM"
    REVISION "202605221625Z"
    DESCRIPTION "Initial version."
    ::= { enterprises 63573 }

trapEvents    OBJECT IDENTIFIER ::= { ntc 0 8 7 }
snmp-srv      OBJECT IDENTIFIER ::= { ntc 0 8 7 }
systemState   OBJECT IDENTIFIER ::= { snmp-srv 1 }
alertObjects  OBJECT IDENTIFIER ::= { snmp-srv 2 }

systemAvailable OBJECT-TYPE
    SYNTAX      DisplayString (SIZE (0..255))
    MAX-ACCESS  read-only
    STATUS      current
    DESCRIPTION
        "Текущая дата и время системы."
    ::= { systemState 1 }

apiAccess OBJECT-TYPE
    SYNTAX      INTEGER { on(1), off(0) }
    MAX-ACCESS  read-only
    STATUS      current
    DESCRIPTION
        "Статус доступа к API сервису. 1 - доступен, 0 - недоступен."
    ::= { systemState 2 }

calcAccess OBJECT-TYPE
    SYNTAX      INTEGER { on(1), off(0) }
    MAX-ACCESS  read-only
    STATUS      current
    DESCRIPTION
        "Статус доступа к Calc сервису. 1 - доступен, 0 - недоступен."
    ::= { systemState 3 }

uiAccess OBJECT-TYPE
    SYNTAX      INTEGER { on(1), off(0) }
    MAX-ACCESS  read-only
    STATUS      current
    DESCRIPTION
        "Статус доступа к UI сервису. 1 - доступен, 0 - недоступен."
    ::= { systemState 4 }

-- Объекты для трапа (alert)

alertTargetName OBJECT-TYPE
    SYNTAX      DisplayString (SIZE (0..255))
    MAX-ACCESS  accessible-for-notify
    STATUS      current
    DESCRIPTION
        "Имя целевого сервиса, вызвавшего событие."
    ::= { alertObjects 1 }

alertTargetType OBJECT-TYPE
    SYNTAX      DisplayString (SIZE (0..255))
    MAX-ACCESS  accessible-for-notify
    STATUS      current
    DESCRIPTION
        "Тип целевого сервиса."
    ::= { alertObjects 2 }

alertHostName OBJECT-TYPE
    SYNTAX      DisplayString (SIZE (0..255))
    MAX-ACCESS  accessible-for-notify
    STATUS      current
    DESCRIPTION
        "Имя хоста, на котором произошло событие."
    ::= { alertObjects 3 }

alertMetricName OBJECT-TYPE
    SYNTAX      DisplayString (SIZE (0..255))
    MAX-ACCESS  accessible-for-notify
    STATUS      current
    DESCRIPTION
        "Имя метрики (например, 'API control')."
    ::= { alertObjects 4 }

alertKeyName OBJECT-TYPE
    SYNTAX      DisplayString (SIZE (0..255))
    MAX-ACCESS  accessible-for-notify
    STATUS      current
    DESCRIPTION
        "Ключ метрики (например, 'API work')."
    ::= { alertObjects 5 }

alertKeyValue OBJECT-TYPE
    SYNTAX      DisplayString (SIZE (0..255))
    MAX-ACCESS  accessible-for-notify
    STATUS      current
    DESCRIPTION
        "Значение ключа (например, описание события)."
    ::= { alertObjects 6 }

alertTimeStamp OBJECT-TYPE
    SYNTAX      DisplayString (SIZE (0..255))
    MAX-ACCESS  accessible-for-notify
    STATUS      current
    DESCRIPTION
        "Временная метка события."
    ::= { alertObjects 7 }

alertSeverity OBJECT-TYPE
    SYNTAX      DisplayString (SIZE (0..255))
    MAX-ACCESS  accessible-for-notify
    STATUS      current
    DESCRIPTION
        "Уровень серьезности (CLEARED, CRITICAL)."
    ::= { alertObjects 8 }

alertMessage OBJECT-TYPE
    SYNTAX      DisplayString (SIZE (0..255))
    MAX-ACCESS  accessible-for-notify
    STATUS      current
    DESCRIPTION
        "Сообщение события."
    ::= { alertObjects 9 }

alertRuleName OBJECT-TYPE
    SYNTAX      DisplayString (SIZE (0..255))
    MAX-ACCESS  accessible-for-notify
    STATUS      current
    DESCRIPTION
        "Имя правила доступа."
    ::= { alertObjects 10 }

alertRuleOwner OBJECT-TYPE
    SYNTAX      DisplayString (SIZE (0..255))
    MAX-ACCESS  accessible-for-notify
    STATUS      current
    DESCRIPTION
        "Владелец правила."
    ::= { alertObjects 11 }

alertMetricValue OBJECT-TYPE
    SYNTAX      DisplayString (SIZE (0..255))
    MAX-ACCESS  accessible-for-notify
    STATUS      current
    DESCRIPTION
        "Значение метрики (может быть пустым)."
    ::= { alertObjects 12 }

alertContext OBJECT-TYPE
    SYNTAX      DisplayString (SIZE (0..255))
    MAX-ACCESS  accessible-for-notify
    STATUS      current
    DESCRIPTION
        "Контекст события (может быть пустым)."
    ::= { alertObjects 13 }

-- ОПРЕДЕЛЕНИЕ TRAP

apiServiceTrap NOTIFICATION-TYPE
    OBJECTS {
        alertTargetName,
        alertTargetType,
        alertHostName,
        alertMetricName,
        alertKeyName,
        alertKeyValue,
        alertTimeStamp,
        alertSeverity,
        alertMessage,
        alertRuleName,
        alertRuleOwner,
        alertMetricValue,
        alertContext
    }
    STATUS current
    DESCRIPTION
        "Trap-сообщение о состоянии сервисов.
         Отправляется при изменении доступности:
         - при восстановлении связи (alertSeverity = CLEARED)
         - при потере связи (alertSeverity = CRITICAL)
         Содержит полную информацию об источнике, времени, правиле и владельце."
    ::= { trapEvents 2 }

-- Соответствие OIDs:
-- alertTargetName        = 1.3.6.1.4.1.63573.0.8.7.2.1
-- alertTargetType        = 1.3.6.1.4.1.63573.0.8.7.2.2
-- alertHostName          = 1.3.6.1.4.1.63573.0.8.7.2.3
-- alertMetricName        = 1.3.6.1.4.1.63573.0.8.7.2.4
-- alertKeyName           = 1.3.6.1.4.1.63573.0.8.7.2.5
-- alertKeyValue          = 1.3.6.1.4.1.63573.0.8.7.2.6
-- alertTimeStamp         = 1.3.6.1.4.1.63573.0.8.7.2.7
-- alertSeverity          = 1.3.6.1.4.1.63573.0.8.7.2.8
-- alertMessage           = 1.3.6.1.4.1.63573.0.8.7.2.9
-- alertRuleName          = 1.3.6.1.4.1.63573.0.8.7.2.10
-- alertRuleOwner         = 1.3.6.1.4.1.63573.0.8.7.2.11
-- alertMetricValue       = 1.3.6.1.4.1.63573.0.8.7.2.12
-- alertContext           = 1.3.6.1.4.1.63573.0.8.7.2.13

END
